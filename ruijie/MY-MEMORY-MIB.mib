-- *****************************************************************
-- MY-MEMORY-MIB.mib:  My Memory MIB file
--
-- $Copyright$
-- 
-- *****************************************************************
--

MY-MEMORY-MIB DEFINITIONS ::= BEGIN

IMPORTS
        MODULE-IDENTITY,
        OBJECT-TYPE,
        NOTIFICATION-TYPE,
        Integer32,
        Counter32
                FROM SNMPv2-SMI
        TruthValue,
        DisplayString,
        RowStatus
                FROM SNMPv2-TC
        MODULE-COMPLIANCE,
        OBJECT-GROUP
                FROM SNMPv2-CONF
        myMgmt
                FROM MY-SMI;

myMemoryMIB MODULE-IDENTITY
        LAST-UPDATED "200310140000Z"
        ORGANIZATION "$Company$"
        CONTACT-INFO
                " 
                Tel: $Telephone$ 

                E-mail: $E-mail$"
        DESCRIPTION
                "This module defines my system mibs."
        REVISION      "200310140000Z"
        DESCRIPTION
                "Initial version of this MIB module."
        ::= { myMgmt 35}

-- Percentage for statistic, etc.
--
Percent ::= TEXTUAL-CONVENTION
    STATUS current
    DESCRIPTION
        "An integer that is in the range of a percent value."
    SYNTAX INTEGER (0..100)
    
myMemoryPoolMIBObjects OBJECT IDENTIFIER ::= { myMemoryMIB 1 }

    
myMemoryPoolUtilizationTable OBJECT-TYPE
  SYNTAX      SEQUENCE OF MyMemoryPoolUtilizationEntry
  MAX-ACCESS  not-accessible
  STATUS      current
  DESCRIPTION
    "A table of memory pool utilization entries. Each of the
     objects provides a general idea of how much of the memory
     pool has been used over a given period of time."
  ::= { myMemoryPoolMIBObjects 1 }

myMemoryPoolUtilizationEntry OBJECT-TYPE
  SYNTAX      MyMemoryPoolUtilizationEntry
  MAX-ACCESS  not-accessible
  STATUS      current
  DESCRIPTION
    "An entry in the memory pool utilization table."
  INDEX { myMemoryPoolIndex }
  ::= { myMemoryPoolUtilizationTable 1 }

MyMemoryPoolUtilizationEntry ::=
  SEQUENCE {
    myMemoryPoolIndex  Integer32,
    myMemoryPoolName   DisplayString,
    myMemoryPoolCurrentUtilization  Percent,
    myMemoryPoolLowestUtilization  Percent,
    myMemoryPoolLargestUtilization Percent
  }
    
myMemoryPoolIndex OBJECT-TYPE
    SYNTAX        Integer32
    MAX-ACCESS    read-only
    STATUS        current
    DESCRIPTION
        "An index that uniquely represents a Memory Pool."
    ::= { myMemoryPoolUtilizationEntry 1 }

myMemoryPoolName OBJECT-TYPE
    SYNTAX        DisplayString
    MAX-ACCESS    read-only
    STATUS        current
    DESCRIPTION
        "A textual name assigned to the memory pool.  This
        object is suitable for output to a human operator"
    ::= { myMemoryPoolUtilizationEntry 2 }
    
myMemoryPoolCurrentUtilization OBJECT-TYPE
    SYNTAX        Percent
    MAX-ACCESS    read-only
    STATUS        current
    DESCRIPTION
        "This is the memory pool utilization currently."
    ::= { myMemoryPoolUtilizationEntry 3 }

myMemoryPoolLowestUtilization OBJECT-TYPE
    SYNTAX        Percent
    MAX-ACCESS    read-only
    STATUS        current
    DESCRIPTION
        "This is the memory pool utilization when memory used least."
    ::= { myMemoryPoolUtilizationEntry 4 }

myMemoryPoolLargestUtilization OBJECT-TYPE
    SYNTAX        Percent
    MAX-ACCESS    read-only
    STATUS        current
    DESCRIPTION
        "This is the memory pool utilization when memory used most."
    ::= { myMemoryPoolUtilizationEntry 5 }
        

myMemoryMIBConformance OBJECT IDENTIFIER ::= { myMemoryMIB 2 }
myMemoryMIBCompliances OBJECT IDENTIFIER ::= { myMemoryMIBConformance 1 }
myMemoryMIBGroups      OBJECT IDENTIFIER ::= { myMemoryMIBConformance 2 }


-- compliance statements

myMemoryMIBCompliance MODULE-COMPLIANCE
        STATUS  current
        DESCRIPTION
                "The compliance statement for entities which implement
                the My Memory MIB"
        MODULE  -- this module
                MANDATORY-GROUPS { myMemoryPoolUtilizationMIBGroup
                 }
        ::= { myMemoryMIBCompliances 1 }
                
-- units of conformance

myMemoryPoolUtilizationMIBGroup OBJECT-GROUP
        OBJECTS {
          myMemoryPoolIndex,
          myMemoryPoolName,
          myMemoryPoolCurrentUtilization,
          myMemoryPoolLowestUtilization,
          myMemoryPoolLargestUtilization
        }
        STATUS  current
        DESCRIPTION
                "A collection of objects providing memory pool utilization to a My agent."
        ::= { myMemoryMIBGroups 1 } 
  
END
